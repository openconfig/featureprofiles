module google-bgp-timers {
  prefix "g-bgp-timers";
  namespace "urn:google:bgp-timers";

  import openconfig-network-instance { prefix oc-netinst; }

  organization "Google, LLC.";
  contact "wenbli@google.com";

  description
    "This module reverts BGP timers to decimal64 instead of uint16 as was
    changed in https://github.com/openconfig/public/pull/604/files.
    This is required in order to assist this backwards-incompatible change due
    to uint16 being represented as a number instead of a string in JSON
    encoding per RFC7951.";

  oc-ext:openconfig-version "0.1.0";

  revision 2022-05-24 {
    description "Initial revision.";
    reference "0.1.0";
  }

  // negotiated-hold-time
  deviation /oc-netinst:network-instances/oc-netinst:network-instance/oc-netinst:protocols/oc-netinst:protocol/oc-netinst:bgp/oc-netinst:neighbors/oc-netinst:neighbor/oc-netinst:timers/oc-netinst:state/oc-netinst:negotiated-hold-time {
    deviate replace {
      type decimal64 {
        fraction-digits 2;
      }
    }
  }

  // stale-routes-time
  deviation /oc-netinst:network-instances/oc-netinst:network-instance/oc-netinst:protocols/oc-netinst:protocol/oc-netinst:bgp/oc-netinst:global/oc-netinst:graceful-restart/oc-netinst:config/oc-netinst:stale-routes-time {
    deviate replace {
      type decimal64 {
        fraction-digits 2;
      }
    }
  }

  deviation /oc-netinst:network-instances/oc-netinst:network-instance/oc-netinst:protocols/oc-netinst:protocol/oc-netinst:bgp/oc-netinst:global/oc-netinst:graceful-restart/oc-netinst:state/oc-netinst:stale-routes-time {
    deviate replace {
      type decimal64 {
        fraction-digits 2;
      }
    }
  }

  deviation /oc-netinst:network-instances/oc-netinst:network-instance/oc-netinst:protocols/oc-netinst:protocol/oc-netinst:bgp/oc-netinst:neighbors/oc-netinst:neighbor/oc-netinst:graceful-restart/oc-netinst:config/oc-netinst:stale-routes-time {
    deviate replace {
      type decimal64 {
        fraction-digits 2;
      }
    }
  }

  deviation /oc-netinst:network-instances/oc-netinst:network-instance/oc-netinst:protocols/oc-netinst:protocol/oc-netinst:bgp/oc-netinst:neighbors/oc-netinst:neighbor/oc-netinst:graceful-restart/oc-netinst:state/oc-netinst:stale-routes-time {
    deviate replace {
      type decimal64 {
        fraction-digits 2;
      }
    }
	}

  deviation /oc-netinst:network-instances/oc-netinst:network-instance/oc-netinst:protocols/oc-netinst:protocol/oc-netinst:bgp/oc-netinst:peer-groups/oc-netinst:peer-group/oc-netinst:graceful-restart/oc-netinst:config/oc-netinst:stale-routes-time {
    deviate replace {
      type decimal64 {
        fraction-digits 2;
      }
    }
	}

  deviation /oc-netinst:network-instances/oc-netinst:network-instance/oc-netinst:protocols/oc-netinst:protocol/oc-netinst:bgp/oc-netinst:peer-groups/oc-netinst:peer-group/oc-netinst:graceful-restart/oc-netinst:state/oc-netinst:stale-routes-time {
    deviate replace {
      type decimal64 {
        fraction-digits 2;
      }
    }
	}

  // connect-retry
  deviation /oc-netinst:network-instances/oc-netinst:network-instance/oc-netinst:protocols/oc-netinst:protocol/oc-netinst:bgp/oc-netinst:neighbors/oc-netinst:neighbor/oc-netinst:timers/oc-netinst:config/oc-netinst:connect-retry {
    deviate replace {
      type decimal64 {
        fraction-digits 2;
      }
    }
	}

  deviation /oc-netinst:network-instances/oc-netinst:network-instance/oc-netinst:protocols/oc-netinst:protocol/oc-netinst:bgp/oc-netinst:neighbors/oc-netinst:neighbor/oc-netinst:timers/oc-netinst:state/oc-netinst:connect-retry {
    deviate replace {
      type decimal64 {
        fraction-digits 2;
      }
    }
	}

  deviation /oc-netinst:network-instances/oc-netinst:network-instance/oc-netinst:protocols/oc-netinst:protocol/oc-netinst:bgp/oc-netinst:peer-groups/oc-netinst:peer-group/oc-netinst:timers/oc-netinst:config/oc-netinst:connect-retry {
    deviate replace {
      type decimal64 {
        fraction-digits 2;
      }
    }
	}

  deviation /oc-netinst:network-instances/oc-netinst:network-instance/oc-netinst:protocols/oc-netinst:protocol/oc-netinst:bgp/oc-netinst:peer-groups/oc-netinst:peer-group/oc-netinst:timers/oc-netinst:state/oc-netinst:connect-retry {
    deviate replace {
      type decimal64 {
        fraction-digits 2;
      }
    }
	}

  // hold-time
  deviation /oc-netinst:network-instances/oc-netinst:network-instance/oc-netinst:protocols/oc-netinst:protocol/oc-netinst:bgp/oc-netinst:neighbors/oc-netinst:neighbor/oc-netinst:timers/oc-netinst:config/oc-netinst:hold-time {
    deviate replace {
      type decimal64 {
        fraction-digits 2;
      }
    }
	}

  deviation /oc-netinst:network-instances/oc-netinst:network-instance/oc-netinst:protocols/oc-netinst:protocol/oc-netinst:bgp/oc-netinst:neighbors/oc-netinst:neighbor/oc-netinst:timers/oc-netinst:state/oc-netinst:hold-time {
    deviate replace {
      type decimal64 {
        fraction-digits 2;
      }
    }
	}

  deviation /oc-netinst:network-instances/oc-netinst:network-instance/oc-netinst:protocols/oc-netinst:protocol/oc-netinst:bgp/oc-netinst:peer-groups/oc-netinst:peer-group/oc-netinst:timers/oc-netinst:config/oc-netinst:hold-time {
    deviate replace {
      type decimal64 {
        fraction-digits 2;
      }
    }
	}

  deviation /oc-netinst:network-instances/oc-netinst:network-instance/oc-netinst:protocols/oc-netinst:protocol/oc-netinst:bgp/oc-netinst:peer-groups/oc-netinst:peer-group/oc-netinst:timers/oc-netinst:state/oc-netinst:hold-time {
    deviate replace {
      type decimal64 {
        fraction-digits 2;
      }
    }
	}

  // keepalive-interval
  deviation /oc-netinst:network-instances/oc-netinst:network-instance/oc-netinst:protocols/oc-netinst:protocol/oc-netinst:bgp/oc-netinst:neighbors/oc-netinst:neighbor/oc-netinst:timers/oc-netinst:config/oc-netinst:keepalive-interval {
    deviate replace {
      type decimal64 {
        fraction-digits 2;
      }
    }
	}

  deviation /oc-netinst:network-instances/oc-netinst:network-instance/oc-netinst:protocols/oc-netinst:protocol/oc-netinst:bgp/oc-netinst:neighbors/oc-netinst:neighbor/oc-netinst:timers/oc-netinst:state/oc-netinst:keepalive-interval {
    deviate replace {
      type decimal64 {
        fraction-digits 2;
      }
    }
	}

  deviation /oc-netinst:network-instances/oc-netinst:network-instance/oc-netinst:protocols/oc-netinst:protocol/oc-netinst:bgp/oc-netinst:peer-groups/oc-netinst:peer-group/oc-netinst:timers/oc-netinst:config/oc-netinst:keepalive-interval {
    deviate replace {
      type decimal64 {
        fraction-digits 2;
      }
    }
	}

  deviation /oc-netinst:network-instances/oc-netinst:network-instance/oc-netinst:protocols/oc-netinst:protocol/oc-netinst:bgp/oc-netinst:peer-groups/oc-netinst:peer-group/oc-netinst:timers/oc-netinst:state/oc-netinst:keepalive-interval {
    deviate replace {
      type decimal64 {
        fraction-digits 2;
      }
    }
	}

  // minimum-advertisement-interval
  deviation /oc-netinst:network-instances/oc-netinst:network-instance/oc-netinst:protocols/oc-netinst:protocol/oc-netinst:bgp/oc-netinst:neighbors/oc-netinst:neighbor/oc-netinst:timers/oc-netinst:config/oc-netinst:minimum-advertisement-interval {
    deviate replace {
      type decimal64 {
        fraction-digits 2;
      }
    }
	}

  deviation /oc-netinst:network-instances/oc-netinst:network-instance/oc-netinst:protocols/oc-netinst:protocol/oc-netinst:bgp/oc-netinst:neighbors/oc-netinst:neighbor/oc-netinst:timers/oc-netinst:state/oc-netinst:minimum-advertisement-interval {
    deviate replace {
      type decimal64 {
        fraction-digits 2;
      }
    }
	}

  deviation /oc-netinst:network-instances/oc-netinst:network-instance/oc-netinst:protocols/oc-netinst:protocol/oc-netinst:bgp/oc-netinst:peer-groups/oc-netinst:peer-group/oc-netinst:timers/oc-netinst:config/oc-netinst:minimum-advertisement-interval {
    deviate replace {
      type decimal64 {
        fraction-digits 2;
      }
    }
	}

  deviation /oc-netinst:network-instances/oc-netinst:network-instance/oc-netinst:protocols/oc-netinst:protocol/oc-netinst:bgp/oc-netinst:peer-groups/oc-netinst:peer-group/oc-netinst:timers/oc-netinst:state/oc-netinst:minimum-advertisement-interval {
    deviate replace {
      type decimal64 {
        fraction-digits 2;
      }
    }
	}
}
